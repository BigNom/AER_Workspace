Attribute VB_Name = "Module2"
Dim oELem As Element
    While oElEnum.MoveNext
        Set oELem = oElEnum.Current
        If oELem.IsGraphical = True Then
            oELem.Color = 2
            oELem.Rewrite
        End If
    Wend
